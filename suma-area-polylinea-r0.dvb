Attribute VB_Name = "Atributos"

Sub Atributo()

1 prg$ = InputBox("Progresiva")
Open "c:\acadprg\progresiva.txt" For Append As #1

Dim p1(0 To 2) As Double 'As Variant
Dim p2(0 To 2) As Double

Dim punto As Variant

'p1(0) = 1.6534
'p1(1) = 1.6534
'p1(2) = 2.5

'GoTo 2000

Dim Block As AcadBlockReference
Dim ReturnObj As AcadObject
Dim ReturnPnt As Variant
 
GetEnt: 'Start loop point
 
 
ActiveDocument.Utility.GetEntity ReturnObj, ReturnPnt, "Select a block: "
 
If ReturnObj.ObjectName <> "AcDbBlockReference" Then
 
MsgBox "The selected object wasn't a block!", vbExclamation
 
GoTo GetEnt 'Goto loop point
 
End If
 
Set Block = ReturnObj

'Set punto = Block.InsertionPoint

x0 = Block.InsertionPoint(0)
y0 = Block.InsertionPoint(1)
Z0 = Block.InsertionPoint(2)

'************************************************************************************************************************************
'Dim punto As Variant
Dim newvarAttributes As Variant
Dim strAttributes As String
    Dim i As Integer
    Dim varAttributes As Variant


 Dim blockObj As AcadBlock
 Dim blockRefObj As AcadBlockReference

Dim layerColl As AcadBlocks
   
Dim ssetObj As AcadSelectionSet

    
Randomize (Timer)
llave$ = "A" + LTrim$(RTrim$(Str$(Int(10000000 * Rnd))))

  Rem MsgBox (llave$)
  
  Rem End
   
   Set ssetObj = ActiveDocument.SelectionSets.Add(llave$)

ssetObj.SelectOnScreen
    
    Dim entry As AcadEntity
        
    For Each entry In ssetObj
     num = num + 1
        a$ = entry.ObjectName
      
'      MsgBox (a$)
    
If a$ = "AcDbBlockReference" Then
Set blockRefObj = entry
     bb$ = entry.Name
    'MsgBox (bb$)
    'p1 = blockRefObj.InsertionPoint
    
    
'MsgBox (blockObj.InsertionPoint(1))
   ' blockRefObj.InsertionPoint
    
    punto = blockRefObj.InsertionPoint()
    
        
   ' MsgBox (punto(1))
    
     Set blockRefObj = entry
    varAttributes = blockRefObj.GetAttributes
     strAttributes = ""
     m = UBound(varAttributes)
    For i = LBound(varAttributes) To UBound(varAttributes)
        strAttributes = strAttributes + "  Tag: " + _
                    varAttributes(i).TagString + vbCrLf + _
                    "   Value: " + varAttributes(i).TextString
    Next i
    
    'MsgBox (strAttributes)
    
    cota$ = (varAttributes(m).TextString)
    
    
    x1 = blockRefObj.InsertionPoint(0)
    y1 = blockRefObj.InsertionPoint(1)
    
  d = Sqr((x0 - x1) ^ 2 + (y0 - y1) ^ 2)
    
    
    If y1 < y0 Then dx = d Else dx = -d
    
    Print #1, prg$, ROUND(dx, 2), Val(cota)
    
             
           
        End If
        
    
 Next entry
        

ssetObj.Delete

Close #1

GoTo 1


End Sub

Attribute VB_Name = "Module1"

Sub suma_region()

Dim Re As AcadRegion

Dim enti As AcadEntity

fm = InputBox("factor multiplicador <1>")

If Val(fm) = 0 Then
fm = 1
Else
fm = Val(fm)
End If

'RE.IntersectWith


Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj

If enti.ObjectName = "AcDbRegion" Then
i = i + 1
Set Re = enti
sum = sum + Abs(Re.Area)
End If
Next

sum = sum * fm

ssetObj.Delete

Dim MyData As DataObject

Set MyData = New DataObject
    
    MyData.SetText Str$(sum)
    MyData.PutInClipboard

MsgBox (i & "  Entidades - Area=" & sum & "  m²" & " factor mult fm=" & fm)

End Sub

Sub areapoly()



'Dim re As AcadPolyline
Dim Re As AcadLWPolyline


Dim enti As AcadEntity



Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0
per = 0
For Each enti In ssetObj


'MsgBox (enti.ObjectName)

If enti.ObjectName = "AcDbPolyline" Then
i = i + 1
Set Re = enti
sum = sum + Abs(Re.Area)
per = per + Abs(Re.Length)
're.Length
End If
Next
ssetObj.Delete

MsgBox (i & "  Entidades   " & sum / 1 & "  m²" + Chr$(13) + _
"Perimetro=" & per)

Dim MyData As DataObject

Set MyData = New DataObject
    
    MyData.SetText Str$(sum)
    MyData.PutInClipboard


End Sub


Sub long_poly()

'Dim re As AcadPolyline
Dim Re As AcadLWPolyline
Dim se As AcadPolyline

Dim enti As AcadEntity


Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj

MsgBox (enti.ObjectName)


If enti.ObjectName = "AcDbPolyline" Then
    i = i + 1
    Set Re = enti
    're.Length
    sum = sum + Abs(Re.Length)
    
End If

If enti.ObjectName = "AcDb2dPolyline" Then
'    MsgBox (enti.ObjectName)
    j = j + 1
    Set se = enti
    're.Length
    sum = sum + Abs(se.Length)
End If




Next

ssetObj.Delete

Dim MyData As DataObject

Set MyData = New DataObject
    
    MyData.SetText Str$(sum)
    MyData.PutInClipboard

MsgBox (i + j & "  Entidades -  Longitud total=" & sum / 1 & "  ml")


End Sub


Sub long_line()

'Dim re As AcadPolyline
Dim Re As AcadLine


Dim enti As AcadEntity



Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj


'MsgBox (enti.ObjectName)

If enti.ObjectName = "AcDbLine" Then
i = i + 1
Set Re = enti
sum = sum + Abs(Re.Length)
End If
Next

ssetObj.Delete

MsgBox (i & "  Entidades lineas Longitud total=" & sum / 1 & "  ml")


Dim MyData As DataObject

Set MyData = New DataObject
    
    MyData.SetText Str$(sum)
    MyData.PutInClipboard

'MsgBox (i & "  Entidades - Area=" & sum & "  m²" & " factor mult fm=" & fm)




End Sub


Sub suma_volumen()

Dim Re As Acad3DSolid


Dim enti As AcadEntity

fm = InputBox("factor multiplicador <1>")

If Val(fm) = 0 Then
fm = 1
Else
fm = Val(fm)
End If


Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

UserForm2.ListBox1.Clear
UserForm2.TextBox2 = ""


For Each enti In ssetObj

'MsgBox (enti.ObjectName)


If enti.ObjectName = "AcDb3dSolid" Then
i = i + 1
Set Re = enti
sum = sum + Abs(Re.Volume)
'MsgBox (Abs(Re.Volume))
UserForm2.TextBox2 = UserForm2.TextBox2 + Str$(Abs(Re.Volume)) + vbCr
UserForm2.ListBox1.AddItem Abs(Re.Volume)


End If
Next

sum = sum * fm

ssetObj.Delete

Dim MyData As DataObject

Set MyData = New DataObject
    
    MyData.SetText Str$(sum)
    MyData.PutInClipboard


UserForm2.Label1.Caption = Str$(i) & "  Entidades - Volumen=" & sum & "  m3" & " factor mult fm=" & fm
UserForm2.TextBox1 = sum
UserForm2.show
MsgBox (i & "  Entidades - Volumen=" & sum & "  m3" & " factor mult fm=" & fm)

End Sub


Sub long_3Dpoly()

'Dim re As AcadPolyline
'Dim re As AcadLWPolyline
Dim Re As Acad3DPolyline


Dim enti As AcadEntity



Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj

'MsgBox (enti.ObjectName)

If enti.ObjectName = "AcDb3dPolyline" Then
i = i + 1
Set Re = enti
're.Length
sum = sum + Abs(Re.Length)
End If
Next

ssetObj.Delete

Dim MyData As DataObject

Set MyData = New DataObject
    
    MyData.SetText Str$(sum)
    MyData.PutInClipboard

MsgBox (i & "  Entidades -  Longitud total=" & sum / 1 & "  ml")


End Sub


Sub area_1()

a1 = Val(InputBox("area 1"))
a2 = Val(InputBox("area 2"))
d = Val(InputBox("area 2"))
'd = 4
r = a2 / a1 * d
MsgBox (r)

End Sub




Sub pendiente()

Dim ssetObj As AcadSelectionSet
Dim txt As AcadText
Dim lin As AcadLine


Randomize (Timer)
llave$ = "A" + LTrim$(RTrim$(Str$(Int(10000000 * Rnd))))

  Rem MsgBox (llave$)
  
  Rem End
   
   Set ssetObj = ActiveDocument.SelectionSets.Add(llave$)

ssetObj.SelectOnScreen
    Dim entry As AcadEntity
        
j = 0
    For Each entry In ssetObj
r = entry.ObjectName

If r = "AcDbLine" Then
Set lin = entry

'lin.Delta

dx = lin.Delta(0)
dy = lin.Delta(1)

'MsgBox ("dx=" & dx)
'MsgBox ("dy=" & dy)

MsgBox ("pend=" & 100 * dy / dx)

End If

Next entry

ssetObj.Delete



End Sub


Sub area2Dpoly()

Dim ReturnPnt As Variant

'Dim re As AcadPolyline
Dim Re As AcadPolyline


Dim enti As AcadEntity


Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0
per = 0
For Each enti In ssetObj


'MsgBox (enti.ObjectName)


If enti.ObjectName = "AcDb2dPolyline" Then
i = i + 1
Set Re = enti
sum = sum + Abs(Re.Area)
per = per + Abs(Re.Length)
're.Length
End If
Next
ssetObj.Delete

'MsgBox (i & "  Entidades   " & sum / 1 & "  m²" + Chr$(13) + _
'"Perimetro=" & per)

Dim MyData As DataObject

Set MyData = New DataObject
    
    MyData.SetText Str$(sum)
    MyData.PutInClipboard


ReturnPnt = ActiveDocument.Utility.GetPoint(, "Entre punto de insercion del Area: ")

Set txt = ActiveDocument.ModelSpace.AddText("A total excavacion = " & Abs(ROUND(sum, 3)), ReturnPnt, 0.4)

'Set txt = ActiveDocument.ModelSpace.AddText("Aexcavacion=" & Ar$ & "m2", p1, 0.4)


End Sub



Sub long_arc()

'Dim re As AcadPolyline
Dim Re As AcadArc

Dim dimObj As AcadDimAligned




Dim enti As AcadEntity



Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj


'MsgBox (enti.ObjectName)

If enti.ObjectName = "AcDbArc" Then
i = i + 1
Set Re = enti

sum = sum + Abs(Re.ArcLength)
End If
Next

ssetObj.Delete

MsgBox (i & "  Entidades Arcos Longitud total=" & sum / 1 & "  ml")


Dim MyData As DataObject

Set MyData = New DataObject
    
    MyData.SetText Str$(sum)
    MyData.PutInClipboard

'MsgBox (i & "  Entidades - Area=" & sum & "  m²" & " factor mult fm=" & fm)





End Sub






Sub long_dim_aligned()

'Dim re As AcadPolyline
Dim Re As AcadDimAligned 'AcadArc

Dim Rf As AcadDimRotated



'Dim dimObj As AcadDimAligned




Dim enti As AcadEntity



Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj


'MsgBox (enti.ObjectName)

If enti.ObjectName = "AcDbAlignedDimension" Then
i = i + 1
Set Re = enti

sum = sum + Abs(Re.Measurement)
End If

If enti.ObjectName = "AcDbRotatedDimension" Then
i = i + 1
Set Rf = enti

sum = sum + Abs(Rf.Measurement)
End If

Next


ssetObj.Delete

MsgBox (i & "  Entidades Dim Longitud total=" & sum / 1 & "  ml")


Dim MyData As DataObject

Set MyData = New DataObject
    
    MyData.SetText Str$(sum)
    MyData.PutInClipboard

'MsgBox (i & "  Entidades - Area=" & sum & "  m²" & " factor mult fm=" & fm)


End Sub






Sub pone_long_poly()

Dim pins As Variant

'Dim re As AcadPolyline
Dim Re As AcadLWPolyline
Dim se As AcadPolyline

Dim txt As AcadText

Dim enti As AcadEntity

Dim pin(0 To 2) As Double

Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj

'MsgBox (enti.ObjectName)


If enti.ObjectName = "AcDbPolyline" Then
    i = i + 1
    Set Re = enti
    're.Length
    sum = sum + Abs(Re.Length)
        pins = ThisDrawing.Utility.GetPoint(, "Punto de Insercion ?:")
    
    Set txt = ActiveDocument.ModelSpace.AddText(Str$(Abs(ROUND(Re.Length, 2))), pins, 1.5)

End If

If enti.ObjectName = "AcDb2dPolyline" Then
'    MsgBox (enti.ObjectName)
    j = j + 1
    Set se = enti
    're.Length
    sum = sum + Abs(se.Length)
    
        pins = ThisDrawing.Utility.GetPoint(, "Punto de Insercion ?:")
    
    Set txt = ActiveDocument.ModelSpace.AddText(Str$(Abs(ROUND(se.Length, 2))), pins, 1.5)

End If




Next

ssetObj.Delete

Dim MyData As DataObject

Set MyData = New DataObject
    
    MyData.SetText Str$(sum)
    MyData.PutInClipboard

MsgBox (i + j & "  Entidades -  Longitud total=" & sum / 1 & "  ml")


End Sub



Public Function ROUND(xx, y)
yy = y + 1
   ROUND = Int(xx * 10 ^ (yy - 1) + 0.5) / 10 ^ (yy - 1)
End Function


Sub prb()

MsgBox (ROUND(10.3255656, 3))
End Sub





Sub txt_areapoly()
'pasa a archivo de texto

'Dim re As AcadPolyline
Dim Re As AcadLWPolyline


Dim enti As AcadEntity

Open "c:\eligio\area.txt" For Output As #1

Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0
per = 0
For Each enti In ssetObj


'MsgBox (enti.ObjectName)

If enti.ObjectName = "AcDbPolyline" Then
i = i + 1
Set Re = enti
z = (Re.Elevation)
are = Abs(Re.Area)

sum = sum + Abs(Re.Area)
per = per + Abs(Re.Length)
're.Length

Print #1, are, z

End If
Next
ssetObj.Delete

MsgBox (i & "  Entidades   " & sum / 1 & "  m²" + Chr$(13) + _
"Perimetro=" & per)

Dim MyData As DataObject

Set MyData = New DataObject
    
    MyData.SetText Str$(sum)
    MyData.PutInClipboard

Close

End Sub



Sub poly_to_xyz()

Open "c:\eligio\puntos.txt" For Output As #1

'Dim re As AcadPolyline
Dim Re As AcadLWPolyline
Dim se As AcadPolyline

Dim enti As AcadEntity

Dim p As Variant


Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj

MsgBox (enti.ObjectName)


If enti.ObjectName = "AcDbPolyline" Then
    i = i + 1
    Set Re = enti
    're.Length
    sum = sum + Abs(Re.Length)
    p = Re.Coordinates
    
    For i = 0 To (UBound(p)) Step 2
    x1 = p(i)
    y1 = p(i + 1)
    Print #1, limpia$(Str$(x1)); ","; limpia$(Str$(y1))
    Next i
    
End If

If enti.ObjectName = "AcDb2dPolyline" Then
'    MsgBox (enti.ObjectName)
    j = j + 1
    Set se = enti
    're.Length
    sum = sum + Abs(se.Length)
End If




Next

ssetObj.Delete

Dim MyData As DataObject

Set MyData = New DataObject
    
    MyData.SetText Str$(sum)
    MyData.PutInClipboard

MsgBox (i + j & "  Entidades -  Longitud total=" & sum / 1 & "  ml")

Close

End Sub

Attribute VB_Name = "Module2"

Sub clayer()

AddExtrudedSolidAlongPath

Dim Re As AcadRegion

Dim enti As AcadEntity

'fm = InputBox("factor multiplicador <1>")

If Val(fm) = 0 Then
fm = 1
Else
fm = Val(fm)
End If


Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj
enti.Layer = "Equipamientos"
Next


ssetObj.Delete


MsgBox (i & "  Entidades - Cambiadas")

End Sub



Sub Ordenar()
Randomize Timer

Dim enti As AcadEntity

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj
'MsgBox (enti.ObjectName)

If enti.ObjectName = "AcDbMText" Or enti.ObjectName = "AcDbText" Then
enti.Layer = "Textos"
'enti.Linetype
enti.Linetype = "ByLAyER"
'enti.color = "ByLAyER"
'enti.TrueColor
End If

If enti.ObjectName = "AcDbRotatedDimension" Then
enti.Layer = "Cotas"
'enti.Linetype
enti.Linetype = "ByLAyER"
'enti.color = "ByLAyER"
'enti.TrueColor
End If

Next

ssetObj.Delete

'Dim MyData As DataObject

'Set MyData = New DataObject
   
'    MyData.SetText Str$(sum)
'    MyData.PutInClipboard

'MsgBox (i & "  Entidades - Area=" & sum & "  m²" & " factor mult fm=" & fm)


End Sub


Sub suma_a_texto()

' le suma un valor constante a un valor texto

sumt = 0.85 '5.217


Randomize Timer

Dim txt As AcadText


Dim enti As AcadEntity

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0


For Each enti In ssetObj
MsgBox (enti.ObjectName)

    If enti.ObjectName = "AcDbText" Then
Set txt = enti
        cota = Val(txt.TextString)
        nuevacota$ = Str$(cota + sumt)
        MsgBox (nuevacota$)
        txt.TextString = nuevacota$
        txt.color = acRed
        txt.Update
    End If

Next

ssetObj.Delete


'MsgBox (i & "  Entidades - Area=" & sum & "  m²" & " factor mult fm=" & fm)


End Sub


Sub enciendelayer_3D()

    Dim a$
    Set layerColl = ActiveDocument.Layers
    
    num = 0
    Dim entry As AcadLayer
    For Each entry In layerColl
     num = num + 1
        a$ = Left$(entry.Name, 2)
If UCase$(a$) = "3D" Then
    entry.LayerOn = True
Else
    entry.LayerOn = False
End If

Next

End Sub


Sub SUMA_TEXTO_EN_OTRO()


' le suma un valor constante a un valor texto

'sumt = 5.217


Randomize Timer

Dim txt As AcadText


Dim enti As AcadEntity

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0


For Each enti In ssetObj
'MsgBox (enti.ObjectName)

    If enti.ObjectName = "AcDbText" Then
Set txt = enti
        cota = Val(txt.TextString)
        SUMA = SUMA + cota
        
    End If

Next

ssetObj.Delete


'MsgBox (i & "  Entidades - Area=" & sum & "  m²" & " factor mult fm=" & fm)



Randomize Timer

'Dim txt As AcadText


'Dim enti As AcadEntity

a = Int(Rnd(Timer) * 10000)

seleccion = Str$(a)
    
    'Dim ssetObj As AcadSelectionSet
    Set ssetObj = ThisDrawing.SelectionSets.Add(seleccion)
    
    ' Add entities to a selection set by prompting user to select on the screen
    ssetObj.SelectOnScreen

a = 0
i = 0


For Each enti In ssetObj
'MsgBox (enti.ObjectName)

    If enti.ObjectName = "AcDbText" Then
Set txt = enti
        'COTA = Val(txt.TextString)
        txt.TextString = Str$(SUMA)
        
    End If

Next

ssetObj.Delete



End Sub

Attribute VB_Name = "Module3"


Function limpia$(a$)
c$ = ""
'MsgBox (a$)
For i = 1 To Len(a$)
k$ = Mid$(a$, i, 1)
If k$ = "," Then k$ = "."
c$ = c$ + k$
Next i
'limpia$ = c$
'p = ROUND(Val(c$), 0)
limpia$ = c$ 'LTrim$(RTrim$(Str$(p)))
End Function

Function puntero_progresiva(b$)

prg$ = InputBox("Progresiva")

Open "c:\acadprg\Puntos.TXT" For Append As #1

    ' Create a new selection set
    Dim sset As AcadSelectionSet
    Set sset = ThisDrawing.SelectionSets.Add("es819")
    
    ' Prompt the user to select objects
    ' and add them to the selection set.
    ' To finish selecting, press ENTER.
    sset.SelectOnScreen
    
    ' Iterate through the selection set
    ' and color each object blue
    Dim entry As AcadEntity
    
    Dim entry12 As AcadPoint
    
    
    
Rem    Punto 0 ************************
    i = 0
    For Each entry In sset
    r$ = entry.ObjectName
    
     Rem MsgBox (r$)     End
    If r$ = "AcDbPoint" Then
        punto1 = punto1 + 1
        Set entry12 = sset(i)
    
        x = entry12.Coordinates(0)
        y = entry12.Coordinates(1)
        z = entry12.Coordinates(2)
    
    
        x0 = x
    
    End If
        
    Next entry
    
sset.Delete
    '********************************************************
    Rem MsgBox (Str$(i) & " puntos cargados ")
    
    'Dim sset As AcadSelectionSet
    Set sset = ThisDrawing.SelectionSets.Add("es819")
    
    ' Prompt the user to select objects
    ' and add them to the selection set.
    ' To finish selecting, press ENTER.
    sset.SelectOnScreen

'sset.SelectOnScreen


i = 0
    For Each entry In sset
    r$ = entry.ObjectName
    
     Rem MsgBox (r$)     End
    If r$ = "AcDbPoint" Then
        
        Set entry12 = sset(i)
    
        x = entry12.Coordinates(0)
        y = entry12.Coordinates(1)
        z = entry12.Coordinates(2)
    
        dx = ROUND(x - x0, 2)
    
        Print #1, prg$, dx, ROUND(y, 3)
        k = k + 1
        
    
    End If
    
        Rem entry.Color = acBlue
        Rem entry.Update
i = i + 1
    Next entry
    
sset.Delete
    
    Rem MsgBox (Str$(i) & " puntos cargados ")

MsgBox (Str$(k) & " puntos cargados ")

Close #1

End Function


Sub A0_puntos_progresiva_poly()

Dim var As Variant
Dim p1(0 To 2) As Double
Dim q1(0 To 2) As Double


prg$ = InputBox("Progresiva")
yy = Val(InputBox("cota terreno"))

Open "c:\acadprg\Puntos_poly.TXT" For Append As #1

    ' Create a new selection set
    Dim sset As AcadSelectionSet
    Set sset = ThisDrawing.SelectionSets.Add("es81911")
    
    ' Prompt the user to select objects
    ' and add them to the selection set.
    ' To finish selecting, press ENTER.
    sset.SelectOnScreen
    
    ' Iterate through the selection set
    ' and color each object blue
    Dim entry As AcadEntity
    
    Dim entry12 As AcadPoint
    
    
    
Rem    Punto 0 ************************
    i = 0
    For Each entry In sset
    r$ = entry.ObjectName
    
     Rem MsgBox (r$)     End
    If r$ = "AcDbPoint" Then
        punto1 = punto1 + 1
        Set entry12 = sset(i)
    
        x = entry12.Coordinates(0)
        y = entry12.Coordinates(1)
        z = entry12.Coordinates(2)
    
    
        x0 = x
        y0 = y
    
    End If
        
    Next entry
    
sset.Delete
    '********************************************************
    Rem MsgBox (Str$(i) & " puntos cargados ")
    
    'Dim sset As AcadSelectionSet
    Set sset = ThisDrawing.SelectionSets.Add("es819217")
    
    ' Prompt the user to select objects
    ' and add them to the selection set.
    ' To finish selecting, press ENTER.
    sset.SelectOnScreen

'sset.SelectOnScreen


i = 0
    For Each entry In sset
    r$ = entry.ObjectName
    
     MsgBox ("La entidad es" & r$): 'End
    '************************************************************************************
    
     If entry.ObjectName = "AcDb2dPolyline" Then
        Set enti_pl1 = entry
        var = enti_pl1.Coordinates
        N = 3 * ((UBound(var)) / 3 - 0)
        For i = LBound(var) To N Step 3
            m = m + 1
            p1(0) = var(i): p1(1) = var(i + 1): p1(2) = var(i + 2)
            xi = -x + p1(0)
            yi = yy + (p1(1) - y0)
            
           ' q1(0) = var(i + 3): q1(1) = var(i + 4): q1(2) = var(i + 5)
            'D = Sqr((p1(0) - q1(0)) ^ 2 + (p1(1) - q1(1)) ^ 2 + (p1(2) - q1(2)) ^ 2)
            'sp = sp + D
            Print #1, prg$, ROUND(xi, 3), ROUND(yi, 3)
        k = k + 1
       Next i
    
        
    
    'MsgBox ("Long=" & sp)
    End If
    
    '************************************************************************************
        
    
        Rem entry.Color = acBlue
        Rem entry.Update
i = i + 1
    Next entry
    
sset.Delete
    
    Rem MsgBox (Str$(i) & " puntos cargados ")

MsgBox (Str$(k) & " puntos cargados ")

Close #1

End Sub

Sub rotula_progresiva()


 Dim ReturnPnt As Variant
 Dim pointObj As AcadPoint
 Dim location(0 To 2) As Double
Dim txt As AcadText
    
m = 30 / 100
yr = 3144.390006
zr = 401.615
    
'X=486329.0513  Yr=7447087.7028  Z=   0.0000
yr = 7447087.7028
10
    ' Return a point using a prompt
    ReturnPnt = ThisDrawing.Utility.GetPoint(, "Enter a point: ")


x = ReturnPnt(0)
y = ReturnPnt(1)
z = ReturnPnt(2)

'pr = pr + 20

r$ = "0+" + Str$(pr)

pr = pr + 20

dx = Abs(yr - y)
dz = m * dx

zz = zr - dz

'zz = 75.15

'MsgBox (zz)

location(0) = CDbl(x)
location(1) = CDbl(y)
location(2) = CDbl(z)

Set txt = ActiveDocument.ModelSpace.AddText(r$, location, 3)

'punto_ayolas

GoTo 10

'ThisDrawing.ModelSpace.AddPolyline (vertices)


End Sub


Sub texto_archivo()

Dim p0 As Variant
Dim p(0 To 2) As Double

Dim tx$(1346)
Dim x(1346)
Dim y(1346)

' Pasa textos a archivo de texto

Randomize Timer

Dim txt As AcadText

Dim enti As AcadEntity

a = Int(Rnd(Timer) * 10000)


seleccion = Str$(a)
    
    Dim ssetObj As AcadSelectionSet
    Set ssetObj = ActiveDocument.SelectionSets.Add(seleccion)
    
    ' Add entities to a selection set by prompting user to select on the screen
    ssetObj.SelectOnScreen

a = 0
i = 0
PUNTERO = 0

For Each enti In ssetObj
'MsgBox (enti.ObjectName)

    If enti.ObjectName = "AcDbText" Then
        PUNTERO = PUNTERO + 1
        Set txt = enti
        cota = Val(txt.TextString)
        SUMA = SUMA + cota
        p0 = txt.InsertionPoint
        x(PUNTERO) = p0(0)
        y(PUNTERO) = p0(1)
        tx$(PUNTERO) = txt.TextString
    End If

Next

m = Ordenar(x, tx$, PUNTERO)

ssetObj.Delete


'MsgBox (i & "  Entidades - Area=" & sum & "  m²" & " factor mult fm=" & fm)

End Sub



Public Function Ordenar(vector1, vector2, PUNT)
      
    Dim iMin    As Long
    Dim iMax    As Long
    Dim Vectemp                    ' -- variable temporal
    Dim Pos     As Long
    Dim i       As Long
      
    iMin = LBound(vector1)
    iMin = 1 'LBound(vector1)
    'iMax = UBound(vector1)
    iMax = PUNT
    
    k = PUNT
      
    While iMax > iMin
        Pos = iMin
        For i = iMin To iMax - 1
            If vector1(i) > vector1(i + 1) Then
            Vectemp1 = vector1(i + 1)
            Vectemp2 = vector2(i + 1)
            vector1(i + 1) = vector1(i)
            vector2(i + 1) = vector2(i)
            vector1(i) = Vectemp1
            vector2(i) = Vectemp2
            Pos = i
            End If
        Next i
        iMax = Pos
    Wend
    
 '   For i = 1 To k
 '   MsgBox (vector1(i))
 '   Next i
    
   Ordenar = 0

Open "c:\acadprg\perfil_text0.txt" For Output As #1
Open "c:\acadprg\perfil_text1.txt" For Output As #2

For i = 1 To k
Print #1, (i * 20 - 20), vector2(i)
Print #2, vector2(i)
Next i

Close

End Function


Sub rotula_piv()
'18/09/2018

'X=486329.0513  Y=7447087.7028  Z=   0.0000
'X=456476.2487  Y=7411323.4537  Z=   0.0000
'X=462385.7512  Y=7413005.8036
x0 = 462385.7512
y0 = 7413005.8036
cota = 98.72 'cota del primer punto


'prg$ = InputBox("Progresiva")

Open "c:\acadprg\PIV.txt" For Output As #1

    ' Create a new selection set
    Dim sset As AcadSelectionSet
    Set sset = ActiveDocument.SelectionSets.Add("es819")
    
    ' Prompt the user to select objects
    ' and add them to the selection set.
    ' To finish selecting, press ENTER.
    sset.SelectOnScreen
    
    ' Iterate through the selection set
    ' and color each object blue
    Dim entry As AcadEntity
    
    Dim entry12 As AcadPoint
    
    
    
Rem    Punto 0 ************************
    i = 0
    For Each entry In sset
    r$ = entry.ObjectName
    
     Rem MsgBox (r$)     End
    If r$ = "AcDbPoint" Then
        punto1 = punto1 + 1
        Set entry12 = entry
    
        x = entry12.Coordinates(0)
        y = (-y0 + entry12.Coordinates(1)) / 10 + cota
        'y = entry12.Coordinates(1) / 10
        z = entry12.Coordinates(2)
 
 
    dx = ROUND(x - x0, 3)
   ' dx = x - x0
    
        Print #1, dx, ROUND(y, 3)
        k = k + 1
                
    
    End If
        
    Next entry
    
sset.Delete
    '********************************************************
    Rem MsgBox (Str$(i) & " puntos cargados ")
    
    'Dim sset As AcadSelectionSet

MsgBox (Str$(k) & " puntos cargados ")

Close #1

End Sub



Sub area_zanja()

Dim p0 As Variant
Dim p1(0 To 2) As Double

Dim minExt As Variant
Dim maxExt As Variant

    
Dim ReturnPnt As Variant

'Dim re As AcadPolyline
Dim Re As AcadPolyline
Dim txt As AcadText

Dim enti As AcadEntity

Randomize Timer

a = Int(Rnd(Timer) * 10000)

seleccion = Str$(a)
    
    Dim ssetObj As AcadSelectionSet
    Set ssetObj = ActiveDocument.SelectionSets.Add(seleccion)
    
    ' Add entities to a selection set by prompting user to select on the screen
    ssetObj.SelectOnScreen

a = 0
i = 0
sum = 0
per = 0
For Each enti In ssetObj


'MsgBox (enti.ObjectName)


If enti.ObjectName = "AcDb2dPolyline" Then
i = i + 1
Set Re = enti
p0 = Re.Coordinates

'MsgBox (UBound(p0))
sum = sum + Abs(Re.Area)
per = per + Abs(Re.Length)

Ar$ = Str$(ROUND(Abs(Re.Area), 4))

x1 = p0(0)
y1 = p0(1)
z1 = p0(2)

x2 = p0(3)
y2 = p0(4)
z2 = p0(5)

x3 = p0(6)
y3 = p0(7)
z3 = p0(8)

x4 = p0(9)
y4 = p0(10)
z4 = p0(11)

xm1 = Abs(x4 - x1)
xm2 = Abs(x3 - x2)

'MsgBox ("xm1=" & xm1 & " xm2=" & xm2)

bm = (xm1 + xm2) / 2

Re.GetBoundingBox minExt, maxExt

h = ROUND(Abs(minExt(1) - maxExt(1)), 3)
'MsgBox (xm1)
bm = ROUND(Abs(Re.Area) / h, 4)

ReturnPnt = ActiveDocument.Utility.GetPoint(, "Entre punto de insercion del Area: ")
p1(0) = ReturnPnt(0)
p1(1) = ReturnPnt(1) - 0.7
p1(2) = ReturnPnt(2)

Set txt = ActiveDocument.ModelSpace.AddText("Aexcavacion=" & Str$(bm) & "*" & Str$(h), ReturnPnt, 0.4)
Set txt = ActiveDocument.ModelSpace.AddText("Aexcavacion=" & Ar$ & "m2", p1, 0.4)

're.Length
End If
Next
ssetObj.Delete

'MsgBox (i & "  Entidades   " & sum / 1 & "  m²" + Chr$(13) + _
'"Perimetro=" & per)

Dim MyData As DataObject

Set MyData = New DataObject
    
    MyData.SetText Str$(sum)
    MyData.PutInClipboard


End Sub


Sub Area_zanja_texto()

' le suma un valor constante a un valor texto

Open "c:\acadprg\area_zanja.txt" For Append As #1


Randomize Timer

Dim txt As AcadText


Dim enti As AcadEntity

a = Int(Rnd(Timer) * 10000)

seleccion = Str$(a)
    
    Dim ssetObj As AcadSelectionSet
    Set ssetObj = ActiveDocument.SelectionSets.Add(seleccion)
    
    ' Add entities to a selection set by prompting user to select on the screen
    ssetObj.SelectOnScreen

a = 0
i = 0


For Each enti In ssetObj
'MsgBox (enti.ObjectName)

    If enti.ObjectName = "AcDbText" Then
    mm = mm + 1
    Set txt = enti
    Print #1, txt.TextString; " ";
    If mm = 2 Then
    mm = 0
    Print #1,
    End If
        
    End If

Next

ssetObj.Delete


'MsgBox (i & "  Entidades - Area=" & sum & "  m²" & " factor mult fm=" & fm)
Close


End Sub

Attribute VB_Name = "Pruebas"
Function listar_dibujos(mi_archivo As String)
'devuelve 1 si el archivo esta abierto
' devuelve 0 en caso contrario

Dim drawing As AcadDocument

listar_dibujos = 0

Control = 0

For Each drawing In ThisDrawing.Application.Documents
    
    MsgBox (drawing.Name)
    
    If drawing.Name = mi_archivo And Control = 0 Then
    MsgBox (drawing.Name)
    Control = 1
    listar_dibujos = 1
    End If

Next

End Function

Function check_archivo(mi_archivo)

Dim drawing As AcadDocument

listar_dibujos = 0

Control = 0
For Each drawing In ThisDrawing.Application.Documents

If drawing.Name = mi_archivo And Control = 0 Then
Control = 1
End If
'MsgBox (drawing.Name)

    If drawing.Active Then
            activeStatus = activeStatus & drawing.Name & " is active." & vbCrLf
    Else
            activeStatus = activeStatus & drawing.Name & " is not active." & vbCrLf
    End If
    Next drawing
    MsgBox activeStatus

listar_dibujos = 1

End Function

Sub check()

MsgBox (listar_dibujos("Dibujo1.dwg"))

End Sub


Sub coordenadas_pantalla()

    Dim sysVarName As String
    Dim sysVarData As Variant
    Dim DataType As Integer
    
    ' Set FILEDIA system variable (data type Integer) to 1. NOTE that
    ' you need to declare a variable as the data type of system variable,
    ' assign data to that variable and then make it variant type
    Dim intData As Integer
    sysVarName = "VIEWSIZE"
    intData = 1
    sysVarData = intData    ' Integer data
'    ThisDrawing.SetVariable sysVarName, sysVarData
    
    ' Check the variable using GetVariable
    sysVarData = ThisDrawing.GetVariable(sysVarName)

MsgBox (sysVarData)

End Sub


Sub punto_polygonal()

Dim XL1 As AcadXline
Dim XL2 As AcadXline

Dim INTPOINT As Variant
Dim INTPOINT2 As Variant

Dim Re As AcadRegion

Dim enti As AcadEntity

'fm = InputBox("factor multiplicador <1>")

If Val(fm) = 0 Then
fm = 1
Else
fm = Val(fm)
End If

'RE.IntersectWith


Randomize Timer

a = Int(Rnd(Timer) * 10000)

seleccion = Str$(a)
    
    Dim ssetObj As AcadSelectionSet
    Set ssetObj = ThisDrawing.SelectionSets.Add(seleccion)
    
    ' Add entities to a selection set by prompting user to select on the screen
    ssetObj.SelectOnScreen

a = 0
i = 0
sum = 0

For Each enti In ssetObj

If enti.ObjectName = "AcDbRegion" Then
i = i + 1
Set Re = enti
sum = sum + Abs(Re.Area)
Dim pins As Variant

pins = ThisDrawing.Utility.GetPoint(, "Punto de Insercion ?:")


x = pins(0)
y = pins(1)


Dim location(0 To 2) As Double
Dim location1(0 To 2) As Double
Dim location2(0 To 2) As Double

location(0) = pins(0)
location(1) = pins(1)
location(2) = pins(2)

location1(0) = pins(0) + 10
location1(1) = pins(1)
location1(2) = pins(2)

location2(0) = pins(0)
location2(1) = pins(1) + 10
location2(2) = pins(2)




Dim PT As AcadPoint

'Set PT = ThisDrawing.ModelSpace.AddPoint(location)

Set XL1 = ActiveDocument.ModelSpace.AddXline(location, location1)
Set XL2 = ActiveDocument.ModelSpace.AddXline(location, location2)


intPoints = XL1.IntersectWith(Re, acExtendNone)

'If VarType(intPoints) <> vbEmpty Then
'        For i = LBound(intPoints) To UBound(intPoints)
'            St = "Intersection Point[" & K & "] is: " & intPoints(J) & "," & intPoints(J + 1) & "," & intPoints(J + 2)
'            MsgBox St, , "IntersectWith Example"
'            St = ""
'            i = i + 2
'            J = J + 3
 '           K = K + 1
'        Next
 '   End If

x1 = intPoints(0)
y1 = intPoints(1)
x2 = intPoints(3)
y2 = intPoints(4)

If x1 < x2 Then xMIN = x1 Else xMIN = x2
If x1 > x2 Then XMAX = x1 Else XMAX = x2


If ((x >= xMIN) And (x <= XMAX)) Then
CHECK1 = 1
Else
CHECK1 = 0
MsgBox ("X=" & x & " x1=" & x1 & " x2=" & x2)

End If

i = 0
j = 0
k = 0

intPoints2 = XL2.IntersectWith(Re, acExtendNone)

'If VarType(intPoints2) <> vbEmpty Then
'        For i = LBound(intPoints2) To UBound(intPoints2)
'            St = "Intersection Point[" & K & "] is: " & intPoints2(J) & "," & intPoints2(J + 1) & "," & intPoints2(J + 2)
'            MsgBox St, , "IntersectWith Example"
'            St = ""
'            i = i + 2
'            J = J + 3
'            K = K + 1
'        Next
'    End If


x1 = intPoints2(0)
y1 = intPoints2(1)
x2 = intPoints2(3)
y2 = intPoints2(4)

If y1 < y2 Then YMIN = y1 Else YMIN = y2
If y1 > y2 Then YMAX = y1 Else YMAX = y2


If ((y >= YMIN) And (y <= YMAX)) Then
CHECK2 = 1
Else
CHECK2 = 0
MsgBox ("y=" & y & " x1=" & y1 & " x2=" & y2)
End If

XL1.Delete
XL2.Delete


MsgBox (CHECK1 & "," & CHECK2)

End If
Next

End Sub





Sub Example_GetSubEntity()
    ' This example prompts the user to select on object on the screen with a mouse click,
    ' and returns some information about the selected object.
    
    Dim Object As Object
    Dim PickedPoint As Variant, TransMatrix As Variant, ContextData As Variant
    Dim HasContextData As String
    
    On Error GoTo NOT_ENTITY
        
TRYAGAIN:
        
    MsgBox "Use the mouse to click on an object in the current drawing after dismissing this dialog box."
        
    ' Get information about selected object
    ThisDrawing.Utility.GetSubEntity Object, PickedPoint, TransMatrix, ContextData
    
    ' Process and display selected object properties
    HasContextData = IIf(VarType(ContextData) = vbEmpty, " does not ", " does ")
    
    MsgBox "The object you chose was an: " & TypeName(Object) & vbCrLf & _
            "Your point of selection was: " & PickedPoint(0) & ", " & _
                                              PickedPoint(1) & ", " & _
                                              PickedPoint(2) & vbCrLf & _
            "This object" & HasContextData & "have nested objects."
    
    Exit Sub
    
NOT_ENTITY:
    ' If you click on empty space or do not select an entity,
    ' this error will be generated
    If MsgBox("You have not selected an object.  Click OK to try again.", _
               vbOKCancel & vbInformation) = vbOK Then
        Resume TRYAGAIN
    End If
End Sub



Sub Example_AddMLine()
   ' This example adds an Mline in model space

    Dim mLineObj As AcadMLine
    Dim vertexList(0 To 17) As Double
   
'mlineobj.
    
    ' Define data for new object
    vertexList(0) = 4: vertexList(1) = 7: vertexList(2) = 0
    vertexList(3) = 5: vertexList(4) = 7: vertexList(5) = 0
    vertexList(6) = 6: vertexList(7) = 7: vertexList(8) = 0
    vertexList(9) = 4: vertexList(10) = 6: vertexList(11) = 0
    vertexList(12) = 5: vertexList(13) = 6: vertexList(14) = 0
    vertexList(15) = 6: vertexList(16) = 6: vertexList(17) = 6

    ' Create the line in model space
    Set mLineObj = ThisDrawing.ModelSpace.AddMLine(vertexList)
     mLineObj.MLineScale = 0.15
     mLineObj.Update
    

    ThisDrawing.Application.ZoomAll
    
    MsgBox "A new MLine has been added to the drawing."
End Sub



Sub cortanCuadrado() 'linea1 As AcadLine, linea2 As AcadLine, conj As AcadSelectionSet) 'As Boolean

    Dim res As Boolean
    Dim aux As Boolean
    Dim i As Integer
    Dim intersec1 As Variant
    Dim intersec2 As Variant
    Dim objBox As Acad3DSolid
   
    res = False
   
    For i = 0 To conj.Count - 1
   
        Set objBox = conj.Item(i)
        intersec1 = objBox.IntersectWith(linea1, acExtendNone)
        intersec2 = objBox.IntersectWith(linea2, acExtendNone)
   
        aux = (UBound(intersec1) > 0) And (UBound(intersec2) > 0)
        res = res Or aux
       
        If aux Then
            Exit For
        End If
           
    Next i
   
   ' cortanCuadrado = res

End Sub


Sub borra_poly()


'Me.Hide

Dim enti As AcadEntity

Randomize Timer

a = Int(Rnd(Timer) * 10000)

seleccion = Str$(a)
    
    Dim ssetObj As AcadSelectionSet
    Set ssetObj = ActiveDocument.SelectionSets.Add(seleccion)
    
    ' Add entities to a selection set by prompting user to select on the screen
    ssetObj.SelectOnScreen


For Each enti In ssetObj

MsgBox (enti.ObjectName)
'aca las entidades polilinea pueden ser Acad2dPolilyne, Acad3dPolyline

'If enti.ObjectName = "AcDbPolyline" Then

If enti.ObjectName = "AcDbPolyline" Or enti.ObjectName = "AcDb2dPolyline" Then
    enti.Delete

End If

Next

ssetObj.Delete

'Me.Show

End Sub



Sub Example_AddExtrudedSolidAlongPath()
    ' This example extrudes a solid from a region
    ' along a path defined by a spline.
    ' The region is created from an arc and a line.
    
    Dim curves(0 To 1) As AcadEntity

    ' Define the arc
    Dim centerPoint(0 To 2) As Double
    Dim radius As Double
    Dim startAngle As Double
    Dim endAngle As Double
    centerPoint(0) = 5#: centerPoint(1) = 3#: centerPoint(2) = 0#
    radius = 2#
    startAngle = 0
    endAngle = 3.141592
    Set curves(0) = ThisDrawing.ModelSpace.AddArc(centerPoint, radius, startAngle, endAngle)
    
    ' Define the line
    Set curves(1) = ThisDrawing.ModelSpace.AddLine(curves(0).startPoint, curves(0).endPoint)
        
    ' Create the region
    Dim regionObj As Variant
    regionObj = ThisDrawing.ModelSpace.AddRegion(curves)
    
    ' Define the extrusion path (spline object)
    Dim splineObj As AcadSpline
    Dim startTan(0 To 2) As Double
    Dim endTan(0 To 2) As Double
    Dim fitPoints(0 To 8) As Double
    
    ' Define the Spline Object
    startTan(0) = 10: startTan(1) = 10: startTan(2) = 10
    endTan(0) = 10: endTan(1) = 10: endTan(2) = 10
    fitPoints(0) = 0: fitPoints(1) = 10: fitPoints(2) = 10
    fitPoints(0) = 10: fitPoints(1) = 10: fitPoints(2) = 10
    fitPoints(0) = 15: fitPoints(1) = 10: fitPoints(2) = 10
    Set splineObj = ThisDrawing.ModelSpace.AddSpline(fitPoints, startTan, endTan)
    
    ' Create the solid
    Dim solidObj As Acad3DSolid
    Set solidObj = ThisDrawing.ModelSpace.AddExtrudedSolidAlongPath(regionObj(0), splineObj)
    ZoomAll
    
End Sub


Public Sub TestAddExtrudedSolidAlongPath()

Dim varPick As Variant
Dim intI As Variant
Dim dblCenter As Variant
Dim dblRadius As Double
Dim objCircle As AcadCircle
Dim objEnts() As AcadEntity
Dim objShape1 As Acad3DSolid
Dim objShape2 As Acad3DSolid
Dim varRegions As Variant
Dim varItem As Variant
Dim entObj As Object
Dim objEnts2() As AcadEntity

'pick path and calculate shape points
With ThisDrawing.Utility
'pick the path
On Error Resume Next
.GetEntity entObj, PntA, vbCrLf & "Selecione una linea: "
If Err Then
MsgBox "No marcaste una linea"
Exit Sub
End If
Set linea = entObj

dblCenter = linea.startPoint

.InitializeUserInput 1 + 2 + 4
dblRadius = .GetDistance(dblCenter, vbCr & "Indicar el radio: ")

End With

'draw the circular region, then extrude along path
With ThisDrawing.ModelSpace

'draw the outer region (circle)
ReDim objEnts(0)
Set objCircle = .AddCircle(dblCenter, dblRadius)
objCircle.Normal = linea.startPoint
Set objEnts(0) = objCircle
'create the region
varRegions = .AddRegion(objEnts)

Set objShape1 = .AddExtrudedSolidAlongPath(varRegions(0), linea)


ReDim objEnts2(0)
dblRadius = dblRadius - 0.008
Set objCircle = .AddCircle(dblCenter, dblRadius)
objCircle.Normal = linea.startPoint
Set objEnts2(0) = objCircle
'create the region
varRegions = .AddRegion(objEnts2)

Set objShape2 = .AddExtrudedSolidAlongPath(varRegions(0), linea)


End With

'delete the temporary geometry
For Each varItem In objEnts: varItem.Delete: Next
For Each varItem In varRegions: varItem.Delete: Next

ThisDrawing.SendCommand "_shade" & vbCr

With ThisDrawing.Utility

'highlight entity
objShape1.Highlight True
objShape1.Update



'exit if they're the same
If objShape1 Is objShape2 Then
MsgBox "Debes seleccionar diferentes solidos"
Exit Sub
End If

'highlight entity
objShape2.Highlight True
objShape2.Update


objShape1.Boolean acSubtraction, objShape2

'highlight entity
objShape1.Highlight False
objShape1.Update
End With


End Sub


Sub tubo3d()

Dim varPick As Variant
Dim intI As Variant
Dim dblCenter As Variant
Dim dblRadius As Double
Dim objCircle As AcadCircle
Dim objEnts() As AcadEntity
Dim objShape1 As Acad3DSolid
Dim objShape2 As Acad3DSolid
Dim varRegions As Variant
Dim varItem As Variant
Dim entObj As Object
Dim objEnts2() As AcadEntity
Dim ini As Variant
Dim fin As Variant
Dim vdirector(0 To 2) As Double
'pick path and calculate shape points
With ActiveDocument.Utility
'pick the path
On Error Resume Next
.GetEntity entObj, PntA, vbCrLf & "Selecione una linea: "
If Err Then
MsgBox "No marcaste una linea"
Exit Sub
End If
Set linea = entObj

ini = linea.startPoint
fin = linea.endPoint
longitud = (linea.Length)
longitud = (linea.Length)
incremento = (fin(0) - ini(0))
xv = (fin(0) - ini(0)) / (linea.Length)
yv = (fin(1) - ini(1)) / (linea.Length)
zv = (fin(2) - ini(2)) / (linea.Length)

vdirector(0) = xv
vdirector(1) = yv
vdirector(2) = zv

dblCenter = linea.startPoint

.InitializeUserInput 1 + 2 + 4
dblRadius = .GetDistance(dblCenter, vbCr & "Indicar el radio: ")

End With

'draw the circular region, then extrude along path
With ActiveDocument.ModelSpace

'draw the outer region (circle)
ReDim objEnts(0)
Set objCircle = .AddCircle(dblCenter, dblRadius)
objCircle.Normal = vdirector
objCircle.Update
Set objEnts(0) = objCircle
'create the region
varRegions = .AddRegion(objEnts)

Set objShape1 = .AddExtrudedSolidAlongPath(varRegions(0), linea)


ReDim objEnts2(0)
dblRadius = dblRadius - 0.008
Set objCircle = .AddCircle(dblCenter, dblRadius)
objCircle.Normal = vdirector
objCircle.Update
Set objEnts2(0) = objCircle
'create the region
varRegions = .AddRegion(objEnts2)

Set objShape2 = .AddExtrudedSolidAlongPath(varRegions(0), linea)


End With

'delete the temporary geometry
For Each varItem In objEnts: varItem.Delete: Next
For Each varItem In varRegions: varItem.Delete: Next

ActiveDocument.SendCommand "_shade" & vbCr

With ActiveDocument.Utility

'highlight entity
objShape1.Highlight True
objShape1.Update



'exit if they're the same
If objShape1 Is objShape2 Then
MsgBox "Debes seleccionar diferentes solidos"
Exit Sub
End If

'highlight entity
objShape2.Highlight True
objShape2.Update


objShape1.Boolean acSubtraction, objShape2

'highlight entity
objShape1.Highlight False
objShape1.Update
End With


End Sub




Sub polylinea3d()

Dim offsetObj As Variant
Dim objEnts(0) As AcadEntity
Dim objShape1 As Acad3DSolid
Dim objShape2 As Acad3DSolid
Dim varRegions As Variant
Dim objEnts2(0) As AcadEntity
Dim varStart(2) As Double
Dim varEnd(2) As Double
Dim objEnt As AcadLine
Dim altura As Double
Dim coordenadasPoli As Variant
Dim pl2 As AcadLWPolyline
Dim objEnt2 As AcadLWPolyline
Dim dblInput As Double
Dim varItem As Variant
With ThisDrawing.Utility
'SELECCIONA UNA POLILINEA RECTANGULAR CERRADA
On Error Resume Next
.GetEntity pl2, PntA, vbCrLf & "Seleccione una polilinea: "
If Err Then
MsgBox "No marcaste una polilinea"
Exit Sub
End If

'CALCULA LAS COORDENADAS DE LA POLILINEA RECTANGULAR CERRADA

coordenadasPoli = pl2.Coordinates

'INGRESA LA ALTURA DE LA BASE DE LA CAMARA
dblInput = .GetReal(vbCrLf & "Ingrese a que altura estará la base de la camara de inspección: ")
'DIBUJA EL RECTANGULO A EXTRUIR A LA ALTURA ESPECIFICADA
Set pl2 = ThisDrawing.ActiveLayout.Block.AddLightWeightPolyline(coordenadasPoli)
pl2.Elevation = dblInput
pl2.Closed = True

pl2.Update

'DIBUJA EL RECTANGULO INTERIOR
coordenadasPoli(0) = coordenadasPoli(0) + 0.05
coordenadasPoli(1) = coordenadasPoli(1) - 0.05
coordenadasPoli(2) = coordenadasPoli(2) - 0.05
coordenadasPoli(3) = coordenadasPoli(3) - 0.05
coordenadasPoli(4) = coordenadasPoli(4) - 0.05
coordenadasPoli(5) = coordenadasPoli(5) + 0.05
coordenadasPoli(6) = coordenadasPoli(6) + 0.05
coordenadasPoli(7) = coordenadasPoli(7) + 0.05

'Set objEnt2 = ThisDrawing.ActiveLayout.Block.AddLightWeightPolyline(coordenadasPoli)

'objEnt2.Update

offsetObj = pl2.Offset(-0.5)

'Set objEnt2 = .GetEntity
'offsetObj

'objEnt2.Elevation = dblInput + 0.05
'objEnt2.Closed = True

'objEnt2.Update


varStart(0) = (coordenadasPoli(0) + coordenadasPoli(4)) / 2
varStart(1) = (coordenadasPoli(1) + coordenadasPoli(5)) / 2
varStart(2) = dblInput + 0.05

varEnd(0) = varStart(0)
varEnd(1) = varStart(1)
varEnd(2) = varStart(2) + (1.3 - dblInput - 0.05)

'DIBUJA UNA LINEA QUE SERA LA RUTA A EXTRUIR
Set objEnt = ThisDrawing.ActiveLayout.Block.AddLine(varStart, varEnd)
objEnt.Update

'DEFINE LA REGION 1
Set objEnts(0) = objEnt2

varRegions = ThisDrawing.ModelSpace.AddRegion(offsetObj)
'DIBUJA EL SOLIDO INTERIOR
Set objShape1 = ThisDrawing.ModelSpace.AddExtrudedSolidAlongPath(varRegions(0), objEnt)

objEnt.Delete

For Each varItem In varRegions: varItem.Delete: Next

'DIBUJA UNA SEGUNDA LINEA QUE SERA LA RUTA A EXTRUIR PARA EL OTRO SOLIDO

varStart(0) = (coordenadasPoli(0) + coordenadasPoli(4)) / 2
varStart(1) = (coordenadasPoli(1) + coordenadasPoli(5)) / 2
varStart(2) = dblInput


varEnd(0) = varStart(0)
varEnd(1) = varStart(1)
varEnd(2) = varStart(2) + (1.3 - dblInput)
'DEFINE LA SEGUNDA REGION
Set objEnt = ThisDrawing.ActiveLayout.Block.AddLine(varStart, varEnd)
objEnt.Update

Set objEnts2(0) = pl2

varRegions = ThisDrawing.ModelSpace.AddRegion(objEnts2)
'DIBUJA EL SOLIDO EXTERIOR

Set objShape2 = ThisDrawing.ModelSpace.AddExtrudedSolidAlongPath(varRegions(0), objEnt)

objEnt.Delete

ThisDrawing.SendCommand "_shade" & vbCr

objShape1.Highlight True
objShape1.Update

objShape2.Highlight True
objShape2.Update

objShape2.Boolean acSubtraction, objShape1

'objShape1.Highlight True
'objShape1.Update

pl2.Delete
'objEnt2.Delete

For Each varItem In varRegions: varItem.Delete: Next

End With

End Sub

Sub caja_polilinea3d()

Dim offsetObj As Variant
Dim objEnts(0) As AcadEntity
Dim objShape1 As Acad3DSolid
Dim objShape2 As Acad3DSolid
Dim varRegions As Variant
Dim objEnts2(0) As AcadEntity
Dim varStart(2) As Double
Dim varEnd(2) As Double
Dim objEnt As AcadLine
Dim coordenadasPoli As Variant
Dim pl2 As AcadLWPolyline
Dim objEnt2 As AcadLWPolyline
Dim dblInput As Double
Dim varItem As Variant
With ThisDrawing.Utility
'SELECCIONA UNA POLILINEA RECTANGULAR CERRADA
'On Error Resume Next
.GetEntity pl2, PntA, vbCrLf & "Seleccione una polilinea: "
'If Err Then
'MsgBox "No marcaste una polilinea"
'Exit Sub
'End If

'CALCULA LAS COORDENADAS DE LA POLILINEA RECTANGULAR CERRADA

coordenadasPoli = pl2.Coordinates

'INGRESA LA ALTURA DE LA BASE DE LA CAMARA
dblInput = .GetReal(vbCrLf & "Ingrese a que altura estará la base de la camara de inspección: ")
'DIBUJA EL RECTANGULO A EXTRUIR A LA ALTURA ESPECIFICADA
Set pl2 = ThisDrawing.ActiveLayout.Block.AddLightWeightPolyline(coordenadasPoli)
pl2.Elevation = dblInput + 0.05
pl2.Closed = True

pl2.Update



offsetObj = pl2.Offset(0.05)

pl2.Delete



varStart(0) = (coordenadasPoli(0) + coordenadasPoli(4)) / 2
varStart(1) = (coordenadasPoli(1) + coordenadasPoli(5)) / 2
varStart(2) = dblInput + 0.05

varEnd(0) = varStart(0)
varEnd(1) = varStart(1)
varEnd(2) = varStart(2) + (1.3 - dblInput - 0.05)

'DIBUJA UNA LINEA QUE SERA LA RUTA A EXTRUIR
Set objEnt = ThisDrawing.ActiveLayout.Block.AddLine(varStart, varEnd)
objEnt.Update

'DEFINE LA REGION 1

varRegions = ThisDrawing.ActiveLayout.Block.AddRegion(offsetObj)
'DIBUJA EL SOLIDO INTERIOR
Set objShape1 = ThisDrawing.ModelSpace.AddExtrudedSolidAlongPath(varRegions(0), objEnt)

objEnt.Delete

For Each offsetObj In varRegions: offsetObj.Delete: Next

'DIBUJA LA POLILINEA EXTERIOR

Set pl2 = ThisDrawing.ActiveLayout.Block.AddLightWeightPolyline(coordenadasPoli)
pl2.Elevation = dblInput
pl2.Closed = True

pl2.Update


'DIBUJA UNA SEGUNDA LINEA QUE SERA LA RUTA A EXTRUIR PARA EL OTRO SOLIDO

varStart(0) = (coordenadasPoli(0) + coordenadasPoli(4)) / 2
varStart(1) = (coordenadasPoli(1) + coordenadasPoli(5)) / 2
varStart(2) = dblInput


varEnd(0) = varStart(0)
varEnd(1) = varStart(1)
varEnd(2) = varStart(2) + (1.3 - dblInput)

Set objEnt = ThisDrawing.ActiveLayout.Block.AddLine(varStart, varEnd)
objEnt.Update
'DEFINE LA SEGUNDA REGION
Set objEnts2(0) = pl2

varRegions = ThisDrawing.ModelSpace.AddRegion(objEnts2)
'DIBUJA EL SOLIDO EXTERIOR

Set objShape2 = ThisDrawing.ModelSpace.AddExtrudedSolidAlongPath(varRegions(0), objEnt)

objEnt.Delete
'offsetObj.Select


ThisDrawing.SendCommand "_shade" & vbCr

objShape1.Highlight True
objShape1.Update

objShape2.Highlight True
objShape2.Update

objShape2.Boolean acSubtraction, objShape1

pl2.Delete

For Each varItem In varRegions: varItem.Delete: Next

End With

End Sub

Sub po()

Dim r As AcadRegion

r.Centroid


End Sub

Attribute VB_Name = "UserForm2"
Attribute VB_Base = "0{C21ACE85-B8AB-49A0-96AF-4EE5CC62399B}{C795A676-3A8E-43C2-B6ED-804F5AA6E1F2}"
Attribute VB_GlobalNameSpace = False
Attribute VB_Creatable = False
Attribute VB_PredeclaredId = True
Attribute VB_Exposed = False
Attribute VB_TemplateDerived = False
Attribute VB_Customizable = False

Private Sub CommandButton1_Click()
End
End Sub

Private Sub UserForm_Click()

End Sub
