Attribute VB_Name = "Module1"
Sub Ch3_OpenDrawing()
    Dim dwgName As String
    dwgName = "c:\Program Files\acad2000\sample\campus.dwg"
    If Dir(dwgName) <> "" Then
        ThisDrawing.Application.Documents.Open dwgName
        
    Else
        MsgBox "File " & dwgName & " does not exist."
    End If

End Sub
Sub nn()


End Sub


Sub civiles()

Dim ssetObj As AcadSelectionSet
Dim sset1Obj As AcadSelectionSet
    
       
    Rem Set ssetObj = ThisDrawing.SelectionSets.("TEST_SET123")
    
    ' Create the selection set
    Rem Dim ssetObj As AcadSelectionSet
Randomize (Timer)
llave$ = "A" + LTrim$(RTrim$(Str$(Int(10000000 * Rnd))))

  MsgBox (llave$)
  
  Rem End
   
   Set ssetObj = ThisDrawing.SelectionSets.Add(llave$)
    
    ' Add entities to a selection set by prompting user to select on the screen
    ssetObj.SelectOnScreen
    
  
    num = 0
    Dim entry As AcadEntity
    For Each entry In ssetObj
     num = num + 1
        entry.Layer = 0
        entry.Update
    Next entry
Rem MsgBox (num & "  entidades cambiadas a  " & elev(j) & " en layer " & enti$(j))
ssetObj.Delete

End Sub



Sub run4()

UserForm1.Show

End Sub



Sub Example_Freeze()
    ' This example creates a new layer called "Freeze".
    ' It then displays the status of the Freeze property
    ' for the new layer, toggles the status of the
    ' Freeze property, and again displays it's status.
    ' After running this example, you can check the layer
    ' control on the Object Properties tool bar. It will
    ' show the new layer and the latest Freeze status.
    

    Dim layerObj As AcadLayer
    
    ' Create the new layer
    Set layerObj = ThisDrawing.Layers.Add("Fruta")
    
    ' Display the Freeze status of the new layer
    GoSub DISPLAYSTATUS
    
    ' Toggle the status of the Freeze property for the layer
    layerObj.Freeze = Not (layerObj.Freeze)
    
    ' Display the Freeze status of the new layer
    GoSub DISPLAYSTATUS

    Exit Sub
    
DISPLAYSTATUS:
    If layerObj.Freeze Then
        MsgBox "Layer " & layerObj.Name & " is frozen.", , "Freeze Example"
    Else
        MsgBox "Layer " & layerObj.Name & " is thawed.", , "Freeze Example"
    End If
    Return
        
End Sub

Attribute VB_Name = "UserForm1"
Attribute VB_Base = "0{92313317-060A-4E44-B38E-62FF3768D1B2}{6AA8AAF4-4A42-40B0-ACCC-D6CE976C1A11}"
Attribute VB_Creatable = False
Attribute VB_PredeclaredId = True
Attribute VB_Exposed = False
Attribute VB_TemplateDerived = False
Attribute VB_Customizable = False
Dim ssetObj As AcadSelectionSet


Private Sub CommandButton1_Click()



 


End Sub

Private Sub CommandButton2_Click()

    
       
    Rem Set ssetObj = ThisDrawing.SelectionSets.("TEST_SET123")
    
    ' Create the selection set
    Rem Dim ssetObj As AcadSelectionSet
Randomize (Timer)
llave$ = "A" + LTrim$(RTrim$(Str$(Int(10000000 * Rnd))))

  Rem MsgBox (llave$)
  
  Rem End
   
   Set ssetObj = ThisDrawing.SelectionSets.Add(llave$)
    
    ' Add entities to a selection set by prompting user to select on the screen
    
   UserForm1.Hide
   
    ssetObj.SelectOnScreen
   
   If ssetObj.Count > 0 Then CommandButton3.Enabled = True Else GoTo 2002

2002   UserForm1.Show
    

End Sub

Private Sub CommandButton3_Click()
  
  k$ = ListBox1.Value
  
  
  
  
 Rem MsgBox (k$)
  If k$ = "" Then GoTo 2001
  
    num = 0
    Dim entry As AcadEntity
    For Each entry In ssetObj
     num = num + 1
        entry.Layer = k$
        entry.Update
    Next entry
Rem MsgBox (num & "  entidades cambiadas a  " & elev(j) & " en layer " & enti$(j))
ssetObj.Delete
CommandButton3.Enabled = False


2001

End Sub

Private Sub CommandButton4_Click()
End
End Sub

Private Sub CommandButton5_Click()

UserForm2.Show

End Sub

Private Sub ListBox1_Click()




End Sub

Private Sub ListBox1_DblClick(ByVal Cancel As MSForms.ReturnBoolean)
  k$ = ListBox1.Value

Rem On Error GoTo 3000
 Set layerColl = ThisDrawing.Blocks
    
     
    num = 0
    Dim entry As AcadBlock
    For Each entry In layerColl
     num = num + 1
       a$ = entry.Name
       Rem  MsgBox (a$)
        If a$ = k$ Then
AcPreview1.Preview = entry.Name

MsgBox (ThisDrawing.FullName)
Rem entry.LayerOn = True

Rem ThisDrawing.ActiveLayer = entry:

Rem End
End If
Rem        MsgBox (a$)
Rem        End
    Next entry



GoTo 3001


Rem 3000 Resume 3001

3001


End Sub

Private Sub UserForm_Activate()
ListBox1.Clear
CommandButton3.Enabled = False



Dim layerColl As AcadBlocks
    Set layerColl = ThisDrawing.Blocks
     
    num = 0
    Dim entry As AcadBlock
    
    For Each entry In layerColl
     num = num + 1
        a$ = entry.Name
        Rem If UCase$(Mid$(a$, 1, 5)) = "5_CVL" Or UCase$(Mid$(a$, 1, 2)) = "01" Then
ListBox1.AddItem (a$)
Rem End If
Rem        MsgBox (a$)
Rem        End
    Next entry


End Sub

Private Sub UserForm_Click()

End Sub

Attribute VB_Name = "UserForm2"
Attribute VB_Base = "0{14D0396D-8635-40BD-9D26-BCAE6B85C8CD}{664DA0FF-79A9-4950-A5F3-2A44124BABCA}"
Attribute VB_Creatable = False
Attribute VB_PredeclaredId = True
Attribute VB_Exposed = False
Attribute VB_TemplateDerived = False
Attribute VB_Customizable = False
Private Sub CommandButton3_Click()
UserForm2.Hide

End Sub

Private Sub UserForm_Activate()
ListBox1.Clear
Dim a$(200)

a$(1) = "0"
a$(2) = "Defpoints"
a$(3) = "0_Grl_dim"
a$(4) = "0_Grl_eje"
a$(5) = "0_Grl_grilla"
a$(6) = "0_Grl_grilla_txt"
a$(7) = "0_Grl_sombr"
a$(8) = "0_Grl_simb"
a$(9) = "0_Grl_txt"
a$(10) = "01a_Solid_Red"
a$(11) = "01b_Solid_Yellow"
a$(12) = "01c_Solid_Green"
a$(13) = "01d_Solid_Cyan"
a$(14) = "01e_Solid_Blue"
a$(15) = "01f_Solid_Magenta"
a$(16) = "01g_Solid_White"
a$(17) = "01h_Solid_Reserved"
a$(18) = "02_Dotted_Red"
a$(19) = "02_Dotted_Yelow"
a$(20) = "02a_Dashed_Red"
a$(21) = "02b_Dashed_Yellow"
a$(22) = "02c_Dashed_Green"
a$(23) = "02d_Dashed_Cyan"
a$(24) = "02e_Dashed_Blue"
a$(25) = "02f_Dashed_Magenta"
a$(26) = "02g_Dashed_White"
a$(27) = "04_Center_Red"
a$(28) = "04_Center_Yellow"
a$(29) = "05_Dashed_Reserved"
a$(30) = "06_oof_Red"
a$(31) = "06_oof_Yellow"
a$(32) = "07_Center_Reserved"
a$(33) = "08_oof_Reserved"
a$(34) = "12_Steel_Reserved"
a$(35) = "13_Steel_Dashed"
a$(36) = "13_Steel_Solid"
a$(37) = "14_WS_Dashed"
a$(38) = "14_WS_Solid_R"
a$(39) = "14_WS_Solid_Y"
a$(40) = "15_WS_Reserved"
a$(41) = "16_2 Stage_Solid_G"
a$(42) = "16_2 Stage_Solid_R"
a$(43) = "16_2 Stage_Solid_Y"
a$(44) = "17_2 Satge_Dash_R"
a$(45) = "17_2 Stage_Dash_Y"
a$(46) = "18_2 Stage_Hatch"
a$(47) = "19_2 Stage_Infor"
a$(48) = "19_2 Stage_Reserved"
a$(49) = "23_Cj_Dashed"
a$(50) = "23_Cj_Solid"
a$(51) = "24_Key_Dashed"
a$(52) = "24_Key_Solid"
a$(53) = "30_Rebar_Dashed"
a$(54) = "30_Rebar_Solid"
a$(55) = "31_Rebar_Infor"
a$(56) = "32_Rebar_Reserved"
a$(57) = "35_Archit_Fixture"
a$(58) = "36_Archit_Infor"
a$(59) = "37_Archit_Reserved"
a$(60) = "40_Mech_Equip"
a$(61) = "41_Mech_Infor"
a$(62) = "42_Mech_Reserved"
a$(63) = "49_Tp_Spot_Elev"
a$(64) = "50_Tp_1Unit_Line"
a$(65) = "50_Tp_1Unit_Txt"
a$(66) = "50_Tp_2Unit_Line"
a$(67) = "50_Tp_2Unit_Txt"
a$(68) = "51_Tp_10Unit_line"
a$(69) = "51_Tp_10Unit_Txt"
a$(70) = "51_Tp_5Unit_Line"
a$(71) = "51_Tp_5Unit_Txt"
a$(72) = "52_Tp_Reserved"
a$(73) = "53_Tp_River_Infor"
a$(74) = "53_Tp_River_line"
a$(75) = "53_Tp_Tributaries"
a$(76) = "54_Tp_Boring"
a$(77) = "54_Tp_Boring_Infor"
a$(78) = "54_Tp_Drillholes"
a$(79) = "54_Tp_Instrument"
a$(80) = "55_Tp_Geological"
a$(81) = "56_Tp_Road"
a$(82) = "56_tp_Road_Infor"
a$(83) = "57_Tp_Struct_Infor"
a$(84) = "57_Tp_Structure"
a$(85) = "58_Tp_Back_Fill"
a$(86) = "58_Tp_Excav"
a$(87) = "58_Tp_Excav_Infor"
a$(88) = "59_Tp_Excav_Drain"
a$(89) = "61_Column_Grid"
a$(90) = "62_Column_Infor"
a$(91) = "7_Mec_dim"
a$(92) = "7_Mec_eje"
a$(93) = "7_Mec_sombr"
a$(94) = "7_Mec_simb"
a$(95) = "7_Mec_txt"
a$(96) = "8_Elc_dim"
a$(97) = "8_Elc_eje"
a$(98) = "8_Elc_sombr"
a$(99) = "8_Elc_simb"
a$(100) = "8_Elc_txt"
a$(101) = "99_Lamina"
a$(102) = "99_Lamina_rev"
a$(103) = "99_Lamina_rev_txt"
a$(104) = "5_Cvl_dim"
a$(105) = "5_Cvl_eje"
a$(106) = "5_Cvl_sombr"
a$(107) = "5_Cvl_simb"
a$(108) = "5_Cvl_txt"
a$(109) = "3_Prs_dim"
a$(110) = "3_Prs_eje"
a$(111) = "3_Prs_simb"
a$(112) = "3_Prs_sombr"
a$(113) = "3_Prs_txt"





Dim layerColl As AcadLayers
    Set layerColl = ThisDrawing.Layers
       
    num = 0
    Dim entry As AcadLayer
    
 cant = 0
    For Each entry In layerColl
     num = num + 1
        ka$ = entry.Name
        
        existe = 0
        For j = 1 To 113
        If existe = 1 Then GoTo 20001
        If ka$ = a$(j) Then existe = 1: cant = cant + 1:
20001         Next j
        
        
        If existe = 0 Then
        Rem If UCase$(Mid$(a$, 1, 5)) = "5_CVL" Or UCase$(Mid$(a$, 1, 2)) = "01" Then
        ListBox1.AddItem (ka$): r = entry.Lock
        End If
Rem        MsgBox (a$)
Rem        End
    Next entry
    Label1.Caption = "No validos" + Str$(-cant + num)
Label2.Caption = "Total" + Str$(num) + Str$(u)
End Sub

Private Sub UserForm_Click()

End Sub
