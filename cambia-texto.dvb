Attribute VB_Name = "Module1"

Sub cambia_texto()

Dim a1$(100)

a1$(1) = "AcDbMText"

Dim txt As AcadText

Dim enty As AcadEntity


Nam$ = "inicio"

u = 1
For Each enty In ActiveDocument.ModelSpace
r = enty.ObjectName

If r = "AcDbText" Then
Set txt = enty
r = txt.TextString
If Mid$(r, 1, 1) = "P" And Len(r) < 7 Then
txt.TextString = r + "(0.20x0.15)"
txt.Update
End If
End If

1001 Next enty


End Sub
